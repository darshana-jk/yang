submodule bbf-vdsl-pointers {
  yang-version 1.1;

  belongs-to bbf-vdsl {
    prefix bbf-vdsl;
  }

  import ietf-interfaces {
    prefix if;
  }

  import bbf-fastdsl {
    prefix bbf-fastdsl;
  }

  import bbf-yang-types {
    prefix bbf-yang;
  }

  include bbf-vdsl-base-body;
  include bbf-vdsl-base;

  // 5.1 xDSL Line
  // 5.2 xDSL Channel
  include bbf-vdsl-line;

  // 5.5 Service related profiles
  include bbf-vdsl-service-profiles;

  // 5.6 Spectrum related profiles
  include bbf-vdsl-spectrum-profiles;

  // 5.7 DSL Quality Management related profiles
  include bbf-vdsl-quality-profiles;

  // 8.2 xTU Line Threshold Profile
  // 8.3 xTU Channel Threshold Profile
  // 8.4 xTU Channel Thresholds
  include bbf-vdsl-threshold-management;

  include bbf-vdsl-performance-management;

  organization
    "Broadband Forum <https://www.broadband-forum.org>
     FTTdp (Fiber to the Distribution Point) Work Area";

  contact
    "Comments or questions about this Broadband Forum YANG module
     should be directed to <mailto:help@broadband-forum.org>.

     Editor:      Joey Boyd, ADTRAN
                  <mailto:joey.boyd@adtran.com>

     Editor:      Ken Kerpez, ASSIA, Inc.
                  <mailto:kkerpez@assia-inc.com>

     WA Director: Christopher Croot, BT plc
                  <mailto:chris.croot@bt.com>

     WA Director: Sven Ooghe, Nokia
                  <mailto:sven.ooghe@nokia.com>";

  description
    "This submodule contains a collection of YANG definitions for
     managing Vector of Profiles (VoP) on VDSL interfaces.

     Copyright (c) 2016, 2017 Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-355c1; see
     the TR itself for full legal notices.";

  revision 2017-03-13 {
    description
      "Corrigendum 1 (fixes to the initial revision).
       * Approval Date:    see revision date above.
       * Publication Date: 2017-04-12.";
    reference
      "TR-355c1: YANG Modules for FTTdp Management
                 <https://www.broadband-forum.org/technical/download/
                        TR-355_Corrigendum_1.pdf>";
  }
  revision 2016-07-18 {
    description
      "Initial revision.
       * Approval Date:    see revision date above.
       * Publication Date: 2016-08-05.";
    reference
      "TR-355: YANG Modules for FTTdp Management
               <https://www.broadband-forum.org/technical/download/
                        TR-355.pdf>";
  }


  typedef line-config-vector-ref {
    type leafref {
      path '/bbf-vdsl:vdsl/vectors/line-config-vector/name';
    }
    description
      "xDSL Line Configuration Vector identifier.";
  }

  typedef threshold-template-ref {
    type leafref {
      path '/bbf-vdsl:vdsl/bbf-vdsl:thresholds/bbf-vdsl:threshold-'
         + 'template/bbf-vdsl:name';
    }
    description
      "xDSL Line Threshold Template name.";
  }

  // 5.4 xDSL Line Configuration Vector

  grouping line-config-vector-body {
    description
      "Line Configuration Vector body.";

    // Per-Channel profiles:
    // 5.5 Service related Profiles
    // 5.7 DSL Quality Management related profiles (channel)
    container channel {
      description
        "Channel profiles. All profile identifiers must be 
         configured.";

      leaf downstream-data-rate-profile {
        type bbf-vdsl:downstream-data-rate-profile-ref;
        mandatory true;
        description
          "Downstream Data Rate Profile identifier.";
      }
      leaf upstream-data-rate-profile {
        type bbf-vdsl:upstream-data-rate-profile-ref;
        mandatory true;
        description
          "Upstream Data Rate Profile identifier.";
      }
      leaf impulse-noise-protection-delay-profile {
        type bbf-vdsl:impulse-noise-protection-delay-profile-ref;
        mandatory true;
        description
          "INP-Delay Profile identifier.";
      }
    }

    // 5.6 Spectrum related Profiles
    leaf line-spectrum-profile {
      type bbf-vdsl:line-spectrum-profile-ref;
      mandatory true;
      description
        "Line Spectrum Profile identifier.";
    }
    leaf upstream-power-back-off-profile {
      type bbf-vdsl:upstream-power-back-off-profile-ref;
      mandatory true;
      description
        "UPBO Profile identifier.";
    }
    leaf downstream-power-back-off-profile {
      type bbf-vdsl:downstream-power-back-off-profile-ref;
      mandatory true;
      description
        "DPBO Profile identifier.";
    }
    leaf radio-frequency-interference-profile {
      type bbf-vdsl:radio-frequency-interference-profile-ref;
      mandatory true;
      description
        "RFI Profile identifier.";
    }

    // 5.7 DSL Quality Management related profiles (line)
    leaf noise-margin-profile {
      type bbf-vdsl:noise-margin-profile-ref;
      mandatory true;
      description
        "Noise Margin Profile identifier.";
    }
    leaf virtual-noise-profile {
      if-feature "virtual-noise";
      type bbf-vdsl:virtual-noise-profile-ref;
      mandatory true;
      description
        "Virtual Noise Profile identifier.";
    }
    leaf sos-profile {
      if-feature "sos";
      type bbf-vdsl:sos-profile-ref;
      mandatory true;
      description
        "SOS Profile identifier.";
    }
    leaf impulse-noise-monitoring-profile {
      if-feature "impulse-noise-monitoring";
      type bbf-vdsl:impulse-noise-monitoring-profile-ref;
      mandatory true;
      description
        "INM Profile identifier.";
    }
    leaf re-initialization-policy-profile {
      if-feature "re-initialization-policy";
      type bbf-vdsl:re-initialization-policy-profile-ref;
      mandatory true;
      description
        "Re-Initialization Policy Profile identifier.";
    }
    leaf vectoring-profile {
      if-feature "vectoring";
      type bbf-vdsl:vectoring-profile-ref;
      mandatory true;
      description
        "Vectoring Profile identifier.";
    }
    leaf data-gathering-profile {
      if-feature "data-gathering";
      type bbf-vdsl:data-gathering-profile-ref;
      mandatory true;
      description
        "Data Gathering Profile identifier.";
    }
  }

  augment '/bbf-vdsl:vdsl/bbf-vdsl:vectors' {
    description
      "5.4 xDSL Line Configuration Vector.";

    list line-config-vector {
      key "name";
      description
        "5.4 xDSL Line Configuration Vector";

      leaf name {
        type bbf-yang:string-ascii64;
        description
          "xDSL Line Configuration Vector Identifier.";
      }

      uses line-config-vector-body;
    }
  }

  // 8 Object model for xDSL Performance Threshold Management
  grouping threshold-profile {
    description
      "Defines 15-min and 24hr line and channel profiles.";

    leaf xtu-15min-line-profile {
      type bbf-vdsl:line-threshold-profile-ref;
      mandatory true;
      description
        "15-minute Line Threshold Profile identifier.";
    }

    leaf xtu-24hr-line-profile {
      if-feature "performance-24hr";
      type bbf-vdsl:line-threshold-profile-ref;
      mandatory true;
      description
        "1-day Line Threshold Profile identifier.";
    }

    leaf xtu-15min-channel-threshold-profile {
      type bbf-vdsl:channel-threshold-profile-ref;
      mandatory true;
      description
        "15-minute Channel Threshold Profile identifier.";
    }

    leaf xtu-24hr-channel-threshold-profile {
      if-feature "performance-24hr";
      type bbf-vdsl:channel-threshold-profile-ref;
      mandatory true;
      description
        "1-day Channel Threshold Profile identifier.";
    }
  }

  augment '/bbf-vdsl:vdsl/bbf-vdsl:thresholds' {
    description
      "8 xDSL Performance Threshold Management.";

    // 8.1 xDSL Line Threshold Template
    list threshold-template {
      key "name";
      description
        "8.1 xDSL Line Threshold Template";

      leaf name {
        type bbf-yang:string-ascii64;
        description
          "Template name.";
      }


      container xtu-c {
        description
          "xTU-Central Office threshold profile pointer.";
        uses threshold-profile;
      }
      container xtu-r {
        description
          "xTU-Central Office threshold profile pointer.";
        uses threshold-profile;
      }
    }
  }

  augment '/if:interfaces/if:interface/bbf-fastdsl:line/bbf-vdsl:'
        + 'line' {
    description
      "5.1 Pointer to xDSL Line Configuration Vector,
       8.1 Pointer to xDSL Line Threshold Template.";

    choice profile-config {
      default "no-profiles-attached";
      description
        "No profiles, Direct or Indirect attachment mode.";

      case no-profiles-attached {
        leaf no-profiles-attached {
          type empty;
          description
            "If present, indicates that no profiles are attached
             to this line.";
        }
      }

      case direct-attachment-mode {
        uses line-config-vector-body;
      }

      case indirect-attachment-mode {
        leaf line-config-vector {
          type bbf-vdsl:line-config-vector-ref;
          description
            "xDSL Line Configuration Vector identifier.
             This identifier must be configured if indirect
             attachment mode is used.";
        }
      }
    }

    leaf threshold-template {
      type bbf-vdsl:threshold-template-ref;
      description
        "xDSL Line Threshold Template identifier";
    }
  }
}
